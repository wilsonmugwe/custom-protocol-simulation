CusProto DEFINITIONS ::= BEGIN
MsgType ::= ENUMERATED { request(0), ack(1), response(2), error(3) }
Header ::= SEQUENCE {
  version  INTEGER (0..4294967295),
  type     MsgType,
  seq      INTEGER (0..4294967295),
  length   INTEGER (0..4294967295)
}
Message ::= SEQUENCE {
  header   Header,
  payload  OCTET STRING,
  crc16    INTEGER (0..65535)
}
END
